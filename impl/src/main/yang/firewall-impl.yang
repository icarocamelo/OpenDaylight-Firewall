module firewall-impl {
    yang-version 1;
    namespace "urn:opendaylight:params:xml:ns:yang:firewall:impl";
    prefix "firewall-impl";

    import config { prefix config; revision-date 2013-04-05; }
    import opendaylight-md-sal-binding { prefix md-sal-binding; revision-date 2013-10-28;}

    description
        "Service definition for firewall project";

    revision "2014-12-10" {
        description
            "Initial revision";
    }

    identity firewall {
        base config:module-type;
        config:java-name-prefix Firewall;
    }

    // Augments the 'configuration' choice node under modules/module.
    augment "/config:modules/config:module/config:configuration" {
        case firewall-impl {
            when "/config:modules/config:module/config:type = 'firewall'";
            container data-broker {
                uses config:service-ref {
                    refine type {
                        mandatory true;
                        config:required-identity mdsal:binding-async-data-broker;
                    }
                }
            }
        }
    }
}
