module rule {

    //The yang version - today only 1 version exists. If omitted defaults to 1.
    yang-version 1; 

    //a unique namespace for this toaster module, to uniquely identify it from other modules that may have the same name.
    namespace
      "http://netconfcentral.org/ns/fw"; 

    //a shorter prefix that represents the namespace for references used below
    prefix firewall;

    //Defines the organization which defined / owns this .yang file.
    organization "Netconf Central";

    //defines the primary contact of this yang file.
    contact
      "Icaro Camelo <icamelo@inocybe.com>";

    //provides a description of this .yang file.
    description
      "YANG version of the FIREWALL-MIB.";

    //defines the dates of revisions for this yang file
    revision "2015-09-04" {
      description
        "Firewall module in progress.";
    }
    
    container rule {

      leaf name {
        type string;
        config false;
        mandatory false;
        description
          "The name of firewall rule";
      }

      leaf sourceMacAddress {
        type string;
        config true;
        mandatory false;
        description
          "The MAC address source";
      }

      leaf destinationMacAddress {
        type string;
        config true;
        mandatory false;
        description
          "The MAC address destination";
      }


      leaf sourceIpAddress {
        type string;
        config true;
        mandatory false;
        description
          "The IP address source";
      }

      leaf destinationIpAddress {
        type string;
        config true;
        mandatory false;
        description
          "The IP address destination";
      }
      
      leaf sourcePort {
          type uint16;
          config true;
          mandatory false;
          description
            "The source port";
      }
      
      leaf destinationPort {
          type uint16;
          config true;
          mandatory false;
          description
            "The destination port";
      }

      leaf protocol {
        type enumeration {
          enum "udp" {
            value 1;
            description
              "UDP protocol.";
          }
          enum "tcp" {
            value 2;
            description
              "TCP protocol.";
          }
        }
        config true;
        mandatory false;
      }
      
      leaf action {
          type enumeration {
            enum "block" {
              value 1;
            }
            enum "allow" {
              value 2;
              description
                "TCP protocol.";
            }
          }
          config true;
          mandatory false;
        }
    }
  }
    container firewall {
    	list rule{
    		key "id";
    		uses rule;
      }
    }
}
